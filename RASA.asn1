RPKI-AS-SET-AUTHORIZATION
  { iso(1) identified-organization(3) dod(6) internet(1)
    private(4) enterprise(1) 99999 42 }  -- FIXME: Need real OID

DEFINITIONS IMPLICIT TAGS ::=
BEGIN

-- Imports from other RFCs
-- ASID is defined in RFC 3779 (X.509 Extensions for IP Addresses and AS Identifiers)
-- For compilation, we define it here:
ASID ::= INTEGER (0..4294967295)

-- RASA object identifiers
id-rpki-rasa OBJECT IDENTIFIER ::= { id-rpki 42 }
id-rpki-rasa-set OBJECT IDENTIFIER ::= { id-rpki 42 1 }
id-rpki-rasa-auth OBJECT IDENTIFIER ::= { id-rpki 42 2 }

-- RASA-SET flags
RasaFlags ::= BIT STRING {
    doNotInherit(0),
    authoritative(1)
}

-- RASA-AUTH flags
RasaAuthFlags ::= BIT STRING {
    strictMode(0)
}

-- Fallback mode for RASA-SET
-- Controls how tools handle IRR fallback when RASA-SET is present
FallbackMode ::= ENUMERATED {
    irrFallback(0),    -- Merge RASA members with IRR query (default)
    irrLock(1),        -- Lock to specific IRR database only
    rasaOnly(2)        -- Use only RASA data, ignore IRR
}

-- Propagation scope for peer locking
PropagationScope ::= ENUMERATED {
    unrestricted(0),    -- Can be nested anywhere (default)
    directOnly(1)       -- Only direct inclusion, no nesting/transit
}

-- Authorized entry with propagation constraint
-- Used in RASA-AUTH authorizedIn field
AuthorizedEntry ::= SEQUENCE {
    asSetName        UTF8String,
    propagation      PropagationScope OPTIONAL
    -- If propagation is absent, defaults to unrestricted
}

-- RASA-SET content
RasaSetContent ::= SEQUENCE {
  version          [0] INTEGER DEFAULT 0,
  asSetName            UTF8String,
  containingAS         ASID,
  members              SEQUENCE OF ASID,
  nestedSets           SEQUENCE OF UTF8String OPTIONAL,
  irrSource            UTF8String OPTIONAL,
  fallbackMode         FallbackMode DEFAULT irrFallback,
  flags                RasaFlags OPTIONAL,
  notBefore            GeneralizedTime,
  notAfter             GeneralizedTime
}

-- RASA-AUTH content
-- authorizedAS and authorizedSet are mutually exclusive
-- Using explicit tags to avoid CHOICE type (simpler OpenSSL integration)
RasaAuthContent ::= SEQUENCE {
  version          [0] INTEGER DEFAULT 0,
  authorizedAS     [1] ASID OPTIONAL,
  authorizedSet    [2] UTF8String OPTIONAL,
  authorizedIn         SEQUENCE OF AuthorizedEntry,
  flags                RasaAuthFlags OPTIONAL,
  notBefore            GeneralizedTime,
  notAfter             GeneralizedTime
}

END
